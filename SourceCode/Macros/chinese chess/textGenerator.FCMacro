# -*- coding: utf-8 -*-

from PySide import QtGui, QtCore
import FreeCAD, Draft, Part
from FreeCAD import Base

chessR = 1
chessH = 1
word = '將'
isDiff = True

class InitGUI(QtGui.QMainWindow):
    def __init__(self):
        super(InitGUI, self).__init__()
        self.initUI()
        
        

    def initUI(self):
        # create our window
        # define window     xLoc,yLoc,xDim,yDim
        self.setGeometry(   300, 300, 220, 220)
        self.setWindowTitle(u"產生象棋底座")
        self.setWindowFlags(QtCore.Qt.WindowStaysOnTopHint)
        self.setMouseTracking(True)

        # create Labels
        self.label1 = QtGui.QLabel(u"底座半徑(cm):", self)
        self.label1.setFixedWidth(150)
        self.label1.move(20, 20)
        self.label2 = QtGui.QLabel(u"底座高度(cm):", self)
        self.label2.setFixedWidth(150)
        self.label2.move(20, 60)
        self.label3 = QtGui.QLabel(u"代表角色:", self)
        self.label3.setFixedWidth(150)
        self.label3.move(20, 100)

        self.textInput1 = QtGui.QLineEdit(self)
        self.textInput1.setText("1")
        self.textInput1.setFixedWidth(50)
        self.textInput1.move(150, 20)

        self.textInput2 = QtGui.QLineEdit(self)
        self.textInput2.setText("1")
        self.textInput2.setFixedWidth(50)
        self.textInput2.move(150, 60)

        self.textInput3 = QtGui.QLineEdit(self)
        self.textInput3.setText(u"將")
        self.textInput3.setFixedWidth(50)
        self.textInput3.move(150, 100)

        self.label4 = QtGui.QLabel(u"字體樣式:", self)
        self.label4.setFixedWidth(150)
        self.label4.move(20, 140)

        self.checkDiff = QtGui.QCheckBox(self)
        self.checkDiff.move(100, 140)
        self.checkDiff.setChecked(True)
        self.label4 = QtGui.QLabel(u"凹", self)
        self.label4.setFixedWidth(150)
        self.label4.move(125, 140)
        self.checkDiff.clicked.connect(self.checkD)

        self.checkFuse = QtGui.QCheckBox(self)
        self.checkFuse.move(150, 140)
        self.checkFuse.setChecked(False)
        self.label4 = QtGui.QLabel(u"凸", self)
        self.label4.setFixedWidth(150)
        self.label4.move(175, 140)
        self.checkFuse.clicked.connect(self.checkF)
        

        # Generate button
        GenerateButton = QtGui.QPushButton(u'產生底座!', self)
        GenerateButton.clicked.connect(self.onGenerate)
        #if not self._isSelect:     
        #   saveButton.setDisabled(True)
        
        GenerateButton.move(65, 180)
        # now make the window visible
        self.show()

    def onGenerate(self):
        global chessR, chessH, word # access global variable
        chessR = int(self.textInput1.text())
        chessH = int(self.textInput2.text())
        word = unicode(self.textInput3.text())
        
        makeChess()
        self.close()

    def checkD(self):
        global isDiff
        self.checkDiff.setChecked(True)
        self.checkFuse.setChecked(False)
        isDiff = True

    def checkF(self):
        global isDiff
        self.checkDiff.setChecked(False)
        self.checkFuse.setChecked(True)
        isDiff = False

def makeChess():
	chess10R = chessR*10;
	chess10H = chessH*10;
	cylinder = Part.makeCylinder(chess10R, chess10H, Base.Vector(0,0,0), Base.Vector(0,0,1))

	ss = Draft.makeShapeString(word, "./../fonts/msjh.ttf", chess10H-2, 0)
	ss.Label = "ss"

	CharExtrude = Draft.extrude(ss, Base.Vector(0 ,0 , 1.5))
	CharExtrude.Label = "Ce"

	CharExtrude = Draft.move(CharExtrude, Base.Vector(-(chess10R-1.05)/2, chessR+0.5, chess10H-chessH));
	CharExtrude = Draft.rotate(CharExtrude, 90, Base.Vector(0,0,0), Base.Vector(1,0,0), False)

	Ce = CharExtrude.Shape
	
	if isDiff:		
		diff = cylinder.cut(Ce)
		Part.show(diff)
	else:
		union = cylinder.fuse(Ce)
		Part.show(union)
	
	FreeCAD.ActiveDocument.removeObject(ss.Name)
	FreeCAD.ActiveDocument.removeObject(CharExtrude.Name)

if __name__ == "__main__": #feature will be generated after macro execution
    a = InitGUI()
