# Save *.stl Function
import FreeCAD
import Mesh
import sys
import math
import os
import subprocess


### ---------------------------------- ###
# import statements
from PySide import QtGui, QtCore

# function define
def getPlacement(quat, vect, obj):
  	if quat[3] > -1  and quat[3] < 1:
  	  	delta = math.acos(quat[3])*2.0
  	  	scale = math.sin(delta/2)
  	  	rx = quat[0]/scale
  	  	ry = quat[1]/scale
  	  	rz = quat[2]/scale
  	else:
  	  	delta = 0
  	  	rx = 0
  	  	ry = 0
  	  	rz = 1
  	info0 = "translation "+str(vect.x)+" "+str(vect.y)+" "+str(vect.z)
  	info1 = "rotation "+str(rx)+" "+str(ry)+" "+str(rz)+" "+str(delta)
	
  	return info0+" "+info1 

def saving(fileDirAndName):
  	# some definitions
  	placement = App.Placement(App.Vector(0,0,0),App.Rotation(0,0,0,1))
  	# user need to set this directory where slicing software is located
	OutDir = fileDirAndName
  	
  	visible_objs = []
  	SLICER = "./../Slic3r"  # Put your Slicer program location here
	  	
	os.chdir(SLICER)
  	# Get Objects in document
  	doc = App.ActiveDocument
  	objs = doc.Objects
  	# hide all
  	for obj in objs:
  	   	if obj.ViewObject.isVisible():
  	   	   visible_objs.append(obj)
  	for obj in visible_objs:
  	  	# get volume
  	  	volume = obj.Shape.Volume
  	  	# get Rotation and translation of volume
  	  	quat = obj.Placement.Rotation.Q
  	  	vect = obj.Placement.Base
		
  	  	pinfo = getPlacement(quat,vect,obj)
		
  	  	# reset placement, export it and set at original placement
  	  	oldPlacement = obj.Placement
  	  	obj.Placement = placement
  	  	obj.Placement = oldPlacement
  		
		stlFile = OutDir
  		Mesh.export(visible_objs,stlFile)
  		subprocess.Popen([SLICER + "Slic3r", stlFile], shell=True)

# main code
# get a saving dir and file name 
stlfilename = QtGui.QFileDialog.getSaveFileName(QtGui.qApp.activeWindow(),'Save model file','./../output models/NewModel.stl', filter="stl file (*.stl)")

# check user want to save file (press save button)
if not str(stlfilename[0])=="":
	saving(str(stlfilename[0]))
