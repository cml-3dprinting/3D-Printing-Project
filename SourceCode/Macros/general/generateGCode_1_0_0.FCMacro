############################################################################
# Save *.gcode Macro Function
# Modified by Kelvin on 2016/1/8
############################################################################



############################################################################
# import statements
############################################################################
import FreeCAD
import Mesh
import sys
import math
import functools
import os
import subprocess
from PySide import QtGui, QtCore
############################################################################



############################################################################
# function define
############################################################################
# a function for debugging
def LOG(message):
	FreeCAD.Console.PrintMessage(message + "\n")

# this function is written by IKE
# more information please check "generateSTL.FCMacro"
def getPlacement(quat, vect, obj):
  	if quat[3] > -1  and quat[3] < 1:
  	  	delta = math.acos(quat[3])*2.0
  	  	scale = math.sin(delta/2)
  	  	rx = quat[0]/scale
  	  	ry = quat[1]/scale
  	  	rz = quat[2]/scale
  	else:
  	  	delta = 0
  	  	rx = 0
  	  	ry = 0
  	  	rz = 1
  	info0 = "translation "+str(vect.x)+" "+str(vect.y)+" "+str(vect.z)
  	info1 = "rotation "+str(rx)+" "+str(ry)+" "+str(rz)+" "+str(delta)
	
  	return info0+" "+info1 

# this function is written by IKE
# more information please check "generateSTL.FCMacro"
def generateSTL(fileDirAndName):
  	# some definitions
  	placement = App.Placement(App.Vector(0,0,0),App.Rotation(0,0,0,1))
  	# user need to set this directory where slicing software is located
	OutDir = fileDirAndName

  	visible_objs = []
  	SLICER = "./../Slic3r"  # Put your Slicer program location here
	  	
	os.chdir(SLICER)
  	# Get Objects in document
  	doc = App.ActiveDocument
  	objs = doc.Objects
  	# hide all
  	for obj in objs:
  	   	if obj.ViewObject.isVisible():
  	   	   visible_objs.append(obj)
  	for obj in visible_objs:
  	  	# get volume
  	  	volume = obj.Shape.Volume
  	  	# get Rotation and translation of volume
  	  	quat = obj.Placement.Rotation.Q
  	  	vect = obj.Placement.Base
		
  	  	pinfo = getPlacement(quat,vect,obj)
		
  	  	# reset placement, export it and set at original placement
  	  	oldPlacement = obj.Placement
  	  	obj.Placement = placement
  	  	obj.Placement = oldPlacement
  		
		stlFile = OutDir
  		Mesh.export(visible_objs,stlFile)
  		subprocess.Popen([SLICER + "Slic3r", stlFile], shell=True)

# convert stl to gcode by CuraEngine
def generateGCode(gcodefilename, setting):
	# get temp stl file path & name
	stlfilename = gcodefilename[0:gcodefilename.rfind('/')] + "/temp.stl"

	# generate a temp stl file
	generateSTL(stlfilename)
	
	# put your CuraEngine program location here
	CURAENGINE_PATH = "./../CuraEngine/"
	
	# Call to use CuraEngine
	# cmd format:
	# 	  CuraEngine [-h] [-v] [-m 3x3matrix] [-c <config file>] [-s <settingkey>=<value>] -o <output.gcode> <model.stl>	
	# often just use:
	#	  CuraEngine -o output.gcode model.stl
	#
	# more information please check following link
	# http://github.com/Ultimaker/CuraEngine
	process = subprocess.Popen([CURAENGINE_PATH + "CuraEngine", "-s", setting, "-o", gcodefilename, stlfilename])
	
	# waiting for the process done
	while True:
	    if process.poll() != None:
			break

	# delete the temp stl file
	os.remove(stlfilename)
############################################################################



############################################################################
# Setting Dialog
############################################################################
class Setting_Dialog(QtGui.QDialog):
	Variables = ["layerThickness", "extrusionWidth", "initialLayerSpeed", "printSpeed", "moveSpeed", "infillSpeed", "skinSpeed"]
	#default value
	Values = [0.18, 0.4, 20, 50, 150, 50, 50]
	LENGTH = len(Variables);
	
	def __init__(self):
		super(Setting_Dialog, self).__init__()
		self.setupUi()
		
	def setupUi(self):
		self.setObjectName("Dialog")
		self.setWindowTitle("GCode Setting")
		self.resize(500, 325)
		
		self.Labels = [QtGui.QLabel(self) for _ in range(self.LENGTH)]
		self.Inputs = [QtGui.QLineEdit(self) for _ in range(self.LENGTH)]
		self.Sliders = [QtGui.QSlider(QtCore.Qt.Horizontal) for _ in range(self.LENGTH)]
		
		leftLayout = QtGui.QVBoxLayout()
		midLayout = QtGui.QVBoxLayout()
		rightLayout = QtGui.QVBoxLayout()
		
		for i in range(self.LENGTH):
			self.Labels[i].setText(self.Variables[i])
			leftLayout.addWidget(self.Labels[i])
			
			self.Inputs[i].setText(str(self.Values[i]))
			midLayout.addWidget(self.Inputs[i])
		
			self.Sliders[i].setMinimum(0)
			self.Sliders[i].setMaximum(200)
			self.Sliders[i].setValue(self.Values[i])
			rightLayout.addWidget(self.Sliders[i])
		
		self.OK = QtGui.QPushButton(self)
		self.OK.setObjectName("OK")
		self.OK.setText("OK")
		self.OK.clicked.connect(functools.partial(self.accept, self.LENGTH))
		
		self.Sliders[0].valueChanged.connect(self.slider0_moved)
		self.Sliders[1].valueChanged.connect(self.slider1_moved)
		self.Sliders[2].valueChanged.connect(self.slider2_moved)
		self.Sliders[3].valueChanged.connect(self.slider3_moved)
		self.Sliders[4].valueChanged.connect(self.slider4_moved)
		self.Sliders[5].valueChanged.connect(self.slider5_moved)
		self.Sliders[6].valueChanged.connect(self.slider6_moved)
		
		# Set Layout
		topHalfLayout = QtGui.QHBoxLayout()
		topHalfLayout.addLayout(leftLayout)
		topHalfLayout.addLayout(midLayout)
		topHalfLayout.addLayout(rightLayout)
		mainLayout = QtGui.QVBoxLayout()
		mainLayout.addLayout(topHalfLayout)
		mainLayout.addWidget(self.OK)
		self.setLayout(mainLayout)
	
	def accept(self, LENGTH):
		self.result = ""
		for i in range(LENGTH):
			self.result += self.Labels[i].text() + "=" + self.Inputs[i].text() + " "
		self.close()
		
	def slider0_moved(self, newValue):
		self.Inputs[0].setText(str(newValue))
	
	def slider1_moved(self, newValue):
		self.Inputs[1].setText(str(newValue))	
		
	def slider2_moved(self, newValue):
		self.Inputs[2].setText(str(newValue))
		
	def slider3_moved(self, newValue):
		self.Inputs[3].setText(str(newValue))
		
	def slider4_moved(self, newValue):
		self.Inputs[4].setText(str(newValue))
		
	def slider5_moved(self, newValue):
		self.Inputs[5].setText(str(newValue))
		
	def slider6_moved(self, newValue):
		self.Inputs[6].setText(str(newValue))
############################################################################



############################################################################
# Visualization Dialog
############################################################################
class Visualization_Dialog(QtGui.QDialog):
	def __init__(self):
		super(Visualization_Dialog, self).__init__()
		self.setupUi()
		
	def setupUi(self):
		self.setObjectName("Dialog")
		self.setWindowTitle("Visualization")
		self.resize(250, 100)
		
		self.Text = QtGui.QLabel(self)
		self.Text.setText("If you want to process visualization, please press OK")
		
		self.OK = QtGui.QPushButton(self)
		self.OK.setObjectName("OK")
		self.OK.setText("OK")
		self.OK.clicked.connect(self.accept)
		self.Cancle = QtGui.QPushButton(self)
		self.Cancle.setObjectName("Cancle")
		self.Cancle.setText("Cancle")
		self.Cancle.clicked.connect(self.deny)
		
		bottomHalfLayout = QtGui.QHBoxLayout()
		bottomHalfLayout.addWidget(self.OK)
		bottomHalfLayout.addWidget(self.Cancle)
		
		mainLayout = QtGui.QVBoxLayout()
		mainLayout.addWidget(self.Text)
		mainLayout.addLayout(bottomHalfLayout)
		self.setLayout(mainLayout)
		
	def accept(self):
		#exe = r'C:\3D-Printing-Project\SourceCode\FreeCAD_x86\qtbuild\bin\3DPrinterSimulator.exe'
		exe = "./3DPrinterSimulator.exe"
		# 3DPrinterSimulator.exe must put in "SourceCode\FreeCAD_x86\qtbuild\bin\" file
		path = r"C:\3D-Printing-Project\SourceCode\FreeCAD_x86\qtbuild\bin"
		os.chdir(path)
		subprocess.Popen(exe)
		self.close()
	
	def deny(self):
		self.close()
############################################################################



############################################################################
# main code
############################################################################
# get gcode setting string
setting_dialog = Setting_Dialog()
setting_dialog.exec_()
setting = setting_dialog.result

# the path of output gcode
#OUTPUT_DIR_PATH = "./../output gcodes/"
OUTPUT_DIR_PATH = "./../bin/model/"

# check if a directory exists and create it if necessary
if not os.path.exists(OUTPUT_DIR_PATH):
    os.makedirs(OUTPUT_DIR_PATH)

# get a saving dir and file name 
gcodefileinfo = QtGui.QFileDialog.getSaveFileName(QtGui.qApp.activeWindow(), "Save GCode file", OUTPUT_DIR_PATH + "NewGCode.gcode", filter="gcode file (*.gcode)")

# convert array to str
gcodefilename = gcodefileinfo[0]

# check if user want to save file (press save button)
if not gcodefilename=="":
	# convert stl to gcode by CuraEngine
  	generateGCode(gcodefilename, setting)
	
	# visualization	
	visualization_dialog = Visualization_Dialog()
	visualization_dialog.exec_()
